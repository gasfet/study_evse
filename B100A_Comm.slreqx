# B100A_Comm
DUT의 전자 부분 ( CP, PP라인, CAN통신 라인)을 담당하며
부가기능으로 시스템의 Inlet interface의 제어를 담당한다.

## #1: PWM 제어 기능 (Functional)
EVSE의 PWM신호를 제어하고, 그 형태를 모니터링 및 분석하는 기능
1. PWM 제어 :
2. 모니터링 및 분석 : PWM 신호의 형태를 Waveform형태로 저장하고, Waveform을 분석한 내용은 Control PC의 제어 소프트웨어에 전송하여 사용자가 현재의 충전 상태 및 Waveform을 확인 할 있어야 한다.

## #2: PLC 통신 기능 (Functional)
1. PLC 통신 분석 기능을 제공한다. ( 상세 내용은 TBD )

## #3: CAN 통신 기능 (Functional)
CAN통신 기능 ( 상세 내용은 TBD )
