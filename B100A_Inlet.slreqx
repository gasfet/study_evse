# B100A_Inlet
DUT의 입력을 NTP100A 시스템 내부로 분배하는 기능
DUT의 입력은 전력 부분과 전자 부분으로 분리한다. 
1. 전력 부분 : AC/DC 전력선 , 단상/3상 
2. 전자 부분 : CP, PP라인, CAN통신 라인

## #1: 전력 부분 기능 (Functional)
DUT Plug로 부터 입력되는 각 단자중 전력선을 분리하여 AC/DC Load로 연결한다.
1. CCS1/2, Type1/2 종류에 따른 Inlet 연결 단자 제공
2. 최대 전류 범위 검토 : 예상값 ( 0 ~ 100A @ 360V )
3. 필요에 따라서 전력선 Switching 입력 필요
3.1 전력선 switching 필요 예상 시나리오는, Inlet Interface에서 동시에 여러개의 다양한 DUT Plug를 동시에 제공할 때, 사용되는 전력 라인만 AC/DC Load로 전달하기 위함
4. 활성화된 DUT Inlet에 대한 indicator 표시
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< Inlet Block : DC Power, AC Power >

## #2: 전자 부분 (Functional)
DUT Plug로 부터 입력되는 각 단자중 통신선을 분리하여 통신 Emulator로 연결한다.
1. 통신선 : CP, PP, CAN
2. 통신 Emulator : B100A_Comm(CP Controller or EV Communication emulator or EVSE Communication Tester )
3. 필요에 따라서 Inlet 스위치를 하는 제어 라인을 통신 Emulator로 부터 받을 수 있다.
4. 사용자의 사용 직관성을 위해서 Inlet전면에 indicator가 표함될 수 있다.
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< Inlet Block : Communication, Control >
