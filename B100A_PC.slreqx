# B100A_PC
NTP100A 시스템의 통합 제어 S/W를 운용하는 Computer H/W

## #1: HW 기능 (Functional)
PC의 H/W
1. Serial Port
2. LAN : 외부 인터넷 연결 및 내부 장치 연결
3. VISA
4. USB

## #2: 외부 사용자 Remote 제어 기능 (Functional)
외부 사용자 프로그램에서 NTP100A에 연결하여 제어할 수 있는 방법 제공
1. 외부 제어 예
1.1 VISA Remote Command
1.2 Serial Remote Command

## #3: Control Application 기능 (Functional)
NTP100A의 전체 시스템 통합 제어 프로그램
1. 사용자에게 제공하는 통합 UI 기능
2. 생산 및 내부 검증을 위한 Test 기능
3. Rack 형태로 사용자가 Oscilloscope 또는 Power Meter , Power supply를 추가로 사용할 수 있어, 이에 대한 확장성 제공
