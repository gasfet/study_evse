# B100A_Container
B100A Container는 NTP100A 시스템을 구성하는 Main fram 기능을 수행한다. 
1. Rack형태로 가정한다. 
2. Industrial PC와 Communication 기능, Power Emulator기능, EVSE의 Plug를 담당하는 Interface기능을 담당하는 H/W를 장착하는 구조물이다.

## #1: Mechanical Frame 기능 (Functional)
Rack 시스템은 내부의 서버 시스템의 기구적인 배치를 제공한다.
1. 기구의 안정성
2. 조립 및 분해 가능
3. Rack시스템의 이동
4. 작업자의 PC 조작 편리성

## #2: System Interface 기능 (Functional)
Rack 시스템 내부의 전기적 환경 및 온도(환기), 외부 연결성 제공
1. 외부의 AC전원을 내부 서버 시스템 제공
2. Emergency Stop 기능
3. 접지
4. 외부 internet 연결 제공
5. 내부 온도 제어 ( 내부 전력 Load에 의한 열 발생이 예상됨 )
