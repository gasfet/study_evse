# B100A_Load
DUT의 전력 부분에서 필요한 EV emulator를 위한 Load기능 수행

## #1: AC/DC Load 기능 (Functional)
AC/DC Load 기능 수행 ( 아직 정확인 필요 Spec은 모름 : TBD )
1. AC 최대 입력 범위 : 100A@380V/3phase
2. DC 최대 입력 범위 : 100A@480V
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<Chroma 63800 Series (63802 / 63803 / 63804) >

## #2: Control 기능 (Functional)
외부에서 제어 명령을 통해서 Load는 전류(또는 전자 Load로서 필요한 설정)을 할 수 있어야 한다.
( 여기서는 PC에서 제어하는 것으로 가정함. )
1. Load 동작 모드 설정 : Constant Current Mode, Constant Voltage Mode, Constant Resistance Mode, Constant Power Mode
2. Control 포트 : VISA or Serial or GPIB, etc

## #3: Measure 기능 (Functional)
전자 Load로서 필요한 측정 기능을 수행하며, 그 결과를 PC의 제어 S/W 또는 EV Communication Emulator에 전달해야 한다.
( 여기서는 PC에서 제어하는 것으로 가정함. )
1. 입력 전류, 전압, 역률, etc : TBD
