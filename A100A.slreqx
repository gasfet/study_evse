# A100A
제품 이름 : NTP100A
EVSE Charging System 완제품을 검사하는 통합 시스템이다. 
즉 측정 대상이 되는 DUT : " EVSE Charging System 완제품 "
( 통합 시스템이란 DUT를 검사하는 시스템으로 내부은 여러개의 기능 Block으로 구성이 된다. )

## #7: EVSE Charging System Tester (Container)
EVSE 충전시스템 검사용 장비
1. 측정 대상은 EVSE 충전 완제품이다.
2. EVSE는 AC 충전기와 DC 충전기가 있다.
3. AC 충전기는 각 국가별 Type 1, Type2 등이 있다.
4. DC 충전기는 각 국가별로 CCS1, CCS2 등이 있다.
5. EVSE는 연결 부분은 Power Line부분과 통신 Line부분으로 분류할 수 있다.
6. 검사 시스템은 사용자가 편집한 시나리오 또는 미리 정의된 시나리오에 따라 EVSE를 검사 기능을 제공한다.
7. EVSE충전 시스템 검사 장비의 코드는 "NTP100A"로 한다.
8. EVSE충전 시스템 검사 장비의 이름은 "EVSE Charging Tester"로 한다.
9. NTP100A는 EV Emulator기능을 수행한다.
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< EVSE Charging 검사 시스템 >
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< EVSE Charging Tester Block Diagram >
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< EVSE Charging Tester Physical Layout >

### #9: AC 충전 시스템 검사 (Functional)
설명 추가:
Type 1/2, GB/T, NACS AC모드 충전 시험
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
#### #10: Type 1 (Functional)
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
#### #17: Type 2 (Functional)
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
#### #18: GB/T (Functional)
1. AC GB/T는 목표에 포함되는가?
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
#### #19: NACS (Functional)
1. AC NACS는 목표에 포함되는가?
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
### #11: DC 충전 시스템 검사 (Functional)
설명 추가:
CCS1 CCS2, GB/T, NACS DC모드 충전 시험
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
#### #12: CCS1 검사 (Functional)
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
#### #13: CCS2 검사 (Functional)
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
#### #14: CB/T 검사 (Functional)
1. DC GB/T는 목표에 포함되는가?
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
#### #15: CHAdeMO (Functional)
1. DC CHAdeMO는 목표에 포함되는가?
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
#### #16: NACS 검사 (Functional)
1. DC NACS는 목표에 포함되는가?
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
#### #33: ChaoJi (Functional)
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
#### #34: Megawatt Charging System (Functional)
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
### #20: Power Line 시험 (Functional)
단상/3상 전원

#### #22: 단상 (Functional)
미국/한국
1. 단상 전압 동작 범위 100V ~ 240V
- Rationale: 한국 단상 전압 : 220V
  미국 단상 전압 : 110V
  일본 단상 주파수 : 50Hz/60Hz
  한국 단상 주파수 : 60Hz
  미국 단상 주파수 : 60Hz

#### #31: 3상 시험 (Functional)
유럽은 3상 전압 ( 확인 필요함.)

### #21: 통신 Line 시험 (Functional)
통신 라인에서 3종류가 있다.
1. CAN 통신
1.1 CAN 통신에 대해서는 내용 추가할 것 : TBD
2. Control Pilot(CP)라인을 이용한 통신
(CP)라인 통신에는 PWM방식과 PLC 통신이 있다.
2.1 PWM 통신 ( AC/DC모드 공통 )
2.1.1 PWM통신을 위해서 NTP100A는 PWM신호의 상태를 변화 시킬 수 있어야 하며, PWM신호의 Waveform을 측정 할 수 있어야 한다.
2.1.2 PWM 신호의 Waveform측정 항목
2.1.2.1 시간축 전압 크기
2.1.2.2 Duty Cycle
2.2 PLC 통신 ( 표준에서는 DC만 정의되어 있지만, AC모드 확장을 위해서 기능이 정의되어야 함 )
2.2.1 PLC 통신에 대한 데이터 logging을 사용자가 볼 수 있어야 한다.
2.2.2
3. Proximity Pilot(PP)라인을 이용한 통신
3.1 PP라인 통신이라 함은 커넥터의 물리적 체결 상태를 모니터링 할 수 있고, Use Case 시나리오에서 가상으로 체결 및 단락을 할 수 있어야 한다.

#### #23: Control Pilot 시험 (Functional)
(CP)라인 통신에는 PWM방식과 PLC 통신이 있다.

##### #26: PWM 통신 시험 (Functional)
( AC/DC모드 공통 )
1. PWM통신을 위해서 NTP100A는 PWM신호의 상태를 변화 시킬 수 있어야 하며, PWM신호의 Waveform을 측정 할 수 있어야 한다.
2. PWM 신호의 Waveform측정 항목
2.1 시간축 전압 크기
2.2 Duty Cycle
3. 상용 회로는 PWM제어를 위해서 저항 스위치를 사용한다. ( 참고 내용 )
- Rationale: AC/DC 충전에서 PWM통신은 CP라인의 기본 통신 방식이다.

##### #27: PLC 통신 시험 (Functional)
2.2 PLC 통신 ( 표준에서는 DC만 정의되어 있지만, AC모드 확장을 위해서 기능이 정의되어야 함 )
2.2.1 PLC 통신에 대한 데이터 logging을 사용자가 볼 수 있어야 한다.
2.2.2

#### #24: Proximity Pilot 시험 (Functional)
1 PP라인 통신이라 함은 커넥터의 물리적 체결 상태를 모니터링 할 수 있고, Use Case 시나리오에서 가상으로 체결 및 단락을 할 수 있어야 한다.

#### #25: CAN 시험 (Functional)
1 CAN 통신에 대해서는 내용 추가할 것 : TBD
- Rationale: NACS 및 CB/T에서는 CAN을 표준으로 사용함.

### #28: Use Case 시험 (Functional)
사용자가 설정한 테스터 시나리오 시험이 가능해야함.
1. NTP100A의 UI를 통해서 미리 설정한 EV Emulator (또는 검사 시나리오)를 지정한다.
2. EVSE가 NTP100A에 연결되고, NTP100A에서 시작 버턴을 누르면, 정해진 시나리오에 따라서 검사를 진행하고, 그결과를 Report로 저장된다.
3. 검사가 진행될 때, 각 전기적 특성을 그래프 형태 또는 테이블 형태로 데이터를 log한다.

### #30: EV Emulator (Functional)
( 이 요구 사항은 다른 내용과 중복될 수 있다. 다만 중복된 내용은 해당 요구 사항에서 처리하며, 여기서는 미처 고려사항에서 다루지 못한 내용이 있을때, 이를 추가하기 위해서 작성하였다. )
1. NTP100A는 EV Emulator기능을 수행한다.
2. EV Emulator기능이란.
2.1 DC 충전 모드에서는 EVSE로부터 충전 전류를 받아서 내부의 Battery를 충전하는 역할을 emulation 할 수 있어야 한다.
2.2 내부 Battery의 용량은 EVSE가 최대 전류를 전송할 때, 약 5분정도 이를 수용할 수 있어야 한다. 그 이유는 5분정도면, 최대 전류 상태에서 필요한 내부 검사를 완료 할 수 있을 것으로 예측한다.
2.3 AC 충전 모드에서는 OBC의 역할을 emulation할 수 있어야 한다.

### #32: 측정 대상 (Informational)
NTP100A의 측정 대상이 되는 DUT에 대한 정의
DUT : " EVSE Charging System 완제품 "

## #8: EV 충전 시험 (삭제) (Informational)
EV 충전 시험하는 장비는 목표가 아님.
이 내용은 EVSE Tester의 기능을 고려할때, EV(전기차)에 필요한 기능을 포함하지 않도록 해야 한다.
